--
-- Roamware DRA MIB definition.
-- Release : 1.0
-- Revision date : 26-Aug-2013
--
-- This specification is supplied "AS IS," and no warranty,
-- either expressed or implied, as to the use, operation, condition,
-- or performance of the specification, is made by the publisher.
--
-- Publisher: Roamware Inc., USA
--
-- **************************************************************

Roamware-DRA2-V2-MIB DEFINITIONS ::= BEGIN
IMPORTS
    MODULE-IDENTITY, OBJECT-TYPE, NOTIFICATION-TYPE, enterprises,
    TimeTicks, Counter32, IpAddress, Integer32
        FROM SNMPv2-SMI
    DisplayString
        FROM SNMPv2-TC
    OBJECT-GROUP
        FROM SNMPv2-CONF
	roamware, mobGenSeverity, mobGenDescription, mobGenPoolName, mobGenMachineID,
	mobGenRemoteHostAddr, mobGenRemotePort, mobGenAlarmTime, mobGenThresholdValue,
	mobGenNotificationId, mobGenServiceName, mobGenAlarmType, mobGenProbableCause,
	mobGenCacheName, mobGenErrorText, mobGenThresholdLWM, mobGenThresholdHWM,
	mobGenThresholdArmTime, mobGenThresholdName, mobGenUtilization, mobGenCapacity,
	mobGenSourcePath, mobGenTargetPath, mobGenInstanceName, mobGenRole, mobGenFeatureName,
	mobGenModuleId, mobGenKPIName, mobGenNetwork, mobGenNodeName, mobGenSequenceNumber, mobGenErrorCode,
	mobGenResourceName, mobGenAddressList
		FROM Roamware-SDS-V2-MIB;

dra			MODULE-IDENTITY
	LAST-UPDATED "201202210000Z"
	ORGANIZATION "Roamware Inc."
	CONTACT-INFO "info@roamware.com"
	DESCRIPTION  "This is the top level entry for Roamware DRA 1.0"
	REVISION     "201202210000Z"
	DESCRIPTION  "Initial version."
	::= { roamware 131 }											-- 1.3.6.1.4.1.11150.131

--
-- Cache specific parameters
--
draCacheGroup					OBJECT IDENTIFIER ::= { dra 1 }				-- 1.3.6.1.4.1.11150.131.1

draCommonCacheGroup				OBJECT IDENTIFIER ::= { draCacheGroup 1 }		        -- 1.3.6.1.4.1.11150.131.1.1

draCommonCacheCmdRefresh		OBJECT-TYPE
		   SYNTAX Integer32
		   MAX-ACCESS read-write
		   STATUS current
		   DESCRIPTION
			 "The common dra caches are refreshed when this parameter is SET with a non-zero value.
			 GET on this parameter returns nothing useful."
		   ::= { draCommonCacheGroup 1 }										-- 1.3.6.1.4.1.11150.131.1.1.1

draCommonCacheRefreshTime		OBJECT-TYPE
		   SYNTAX DisplayString
		   MAX-ACCESS read-only
		   STATUS current
		   DESCRIPTION
			 "Returns a string containing the last refresh date/time of dra common caches."
		   ::= { draCommonCacheGroup 2 }										-- 1.3.6.1.4.1.11150.131.1.1.2


draRouteCacheGroup				OBJECT IDENTIFIER ::= { draCacheGroup 2 }		        -- 1.3.6.1.4.1.11150.131.1.2

draRouteCacheCmdRefresh		OBJECT-TYPE
		   SYNTAX Integer32
		   MAX-ACCESS read-write
		   STATUS current
		   DESCRIPTION
			 "The dra route caches are refreshed when this parameter is SET with a non-zero value.
			 GET on this parameter returns nothing useful."
		   ::= { draRouteCacheGroup 1 }										-- 1.3.6.1.4.1.11150.131.1.2.1

draRouteCacheRefreshTime		OBJECT-TYPE
		   SYNTAX DisplayString
		   MAX-ACCESS read-only
		   STATUS current
		   DESCRIPTION
			 "Returns a string containing the last refresh date/time of dra route caches."
		   ::= { draRouteCacheGroup 2 }										-- 1.3.6.1.4.1.11150.131.1.2.2

END
