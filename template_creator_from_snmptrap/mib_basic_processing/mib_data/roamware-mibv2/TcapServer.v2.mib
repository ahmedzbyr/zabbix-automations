--
-- Roamware TCAP Server MIB definition.
-- Release : 
-- Revision : 
-- Revision date : 
--
-- This specification is supplied "AS IS," and no warranty, 
-- either expressed or implied, as to the use, operation, condition,
-- or performance of the specification, is made by the publisher.
--
-- Publisher: Roamware Inc., USA
-- **************************************************************


Roamware-tcapServer-V2-MIB DEFINITIONS ::= BEGIN
IMPORTS
    MODULE-IDENTITY, OBJECT-TYPE, NOTIFICATION-TYPE,
    TimeTicks, Counter32
        FROM SNMPv2-SMI
    DisplayString
        FROM SNMPv2-TC
    OBJECT-GROUP
        FROM SNMPv2-CONF
    roamware, mobGenNotificationId, mobGenSeverity, 
    mobGenDescription, mobGenMachineID, mobGenServiceName, 
    mobGenAlarmTime, mobGenAlarmType, mobGenProbableCause, 
    mobGenThresholdName, mobGenThresholdValue, mobGenThresholdLWM, mobGenThresholdHWM, 
    mobGenUtilization, mobGenCapacity, mobGenThresholdArmTime, mobGenSequenceNumber
	FROM Roamware-SDS-V2-MIB;


tcapServer-mob      MODULE-IDENTITY   
                    LAST-UPDATED "200711201256Z"
                    ORGANIZATION "Roamware Inc."
                    CONTACT-INFO "info@roamware.com"
                    DESCRIPTION  "This is the top level entry for Roamware TcapServer."
                    REVISION "200711201256Z"
              	    DESCRIPTION  "Initial version."
            ::= { roamware 83 }                                  -- 1.3.6.1.4.1.11150.83

--
-- tcapServer specific status reports
--
tcapServerStatus	   OBJECT IDENTIFIER ::= { tcapServer-mob 1 }	 -- 1.3.6.1.4.1.11150.83.1


tcapServerLegsInUse	OBJECT-TYPE
		   SYNTAX INTEGER
		   MAX-ACCESS accessible-for-notify
		   STATUS current
		   DESCRIPTION
			 "This variable represents the total number of legs currently assigned to all dialogs."
		   ::= { tcapServerStatus 1 }					   -- 1.3.6.1.4.1.11150.83.1.1

tcapServerDialogsInUse		OBJECT-TYPE
		   SYNTAX INTEGER
		   MAX-ACCESS accessible-for-notify
		   STATUS current
		   DESCRIPTION
			 "This variable represents the number of dialogs currently in use."
		   ::= { tcapServerStatus 2 }					   -- 1.3.6.1.4.1.11150.83.1.2

tcapServerInBusMsgQCount		OBJECT-TYPE
		   SYNTAX INTEGER
		   MAX-ACCESS accessible-for-notify
		   STATUS current
		   DESCRIPTION
			 "This variable represents the current queue size of the messages being received from the bus."
		   ::= { tcapServerStatus 3 }					   -- 1.3.6.1.4.1.11150.83.1.3

tcapServerDBConnectionStatus	OBJECT-TYPE
		   SYNTAX INTEGER
		   {
				up(1),
				down(0)
		   }
		   MAX-ACCESS accessible-for-notify
		   STATUS current
		   DESCRIPTION
			 "This variable indicates whether the database is connected or not."
		   ::= { tcapServerStatus 4 }					   -- 1.3.6.1.4.1.11150.83.1.4

tcapServerBusConnectionStatus	OBJECT-TYPE
		   SYNTAX INTEGER
		   {
				up(1),
				down(0)
		   }
		   MAX-ACCESS accessible-for-notify
		   STATUS current
		   DESCRIPTION
			 "This variable indicates whether the bus is connected or not."
		   ::= { tcapServerStatus 5 }					   -- 1.3.6.1.4.1.11150.83.1.5

tcapServerSS7MsgQCount		OBJECT-TYPE
		   SYNTAX INTEGER
		   MAX-ACCESS accessible-for-notify
		   STATUS current
		   DESCRIPTION
			 "This variable represents the current queue size of the SS7 messages."
		   ::= { tcapServerStatus 6 }					   -- 1.3.6.1.4.1.11150.83.1.6

tcapServerBusSubscriptionStatus		OBJECT-TYPE
		   SYNTAX INTEGER
		   MAX-ACCESS accessible-for-notify
		   STATUS current
		   DESCRIPTION
			 "This variable provides subscription status of channels."
		   ::= { tcapServerStatus 7 }					   -- 1.3.6.1.4.1.11150.83.1.7

--
-- TCAP Server aggregate statistics
-- All counts are for the last minute only.
--
tcapServerAggregateStatistics OBJECT IDENTIFIER ::= { tcapServer-mob 2 }    -- 1.3.6.1.4.1.11150.83.2

tcapServerStatNewDialogs			OBJECT-TYPE
		   SYNTAX INTEGER
		   MAX-ACCESS accessible-for-notify
		   STATUS current
		   DESCRIPTION
              "This variable represents the number of new dialogs created in the last minute."
		   ::= { tcapServerAggregateStatistics 1 }					   -- 1.3.6.1.4.1.11150.83.2.1

tcapServerStatNewLegs				OBJECT-TYPE
		   SYNTAX INTEGER
		   MAX-ACCESS accessible-for-notify
		   STATUS current
		   DESCRIPTION
              "This variable represents the number of new legs created in the last minute."
		   ::= { tcapServerAggregateStatistics 2 }					   -- 1.3.6.1.4.1.11150.83.2.2

tcapServerStatAppInitedDlgs			OBJECT-TYPE
		   SYNTAX INTEGER
		   MAX-ACCESS accessible-for-notify
		   STATUS current
		   DESCRIPTION
              "This variable provides the number of dialogs initiated by application in the last minute."
		   ::= { tcapServerAggregateStatistics 3 }					   -- 1.3.6.1.4.1.11150.83.2.3

tcapServerStatDlgsReleased			OBJECT-TYPE
		   SYNTAX INTEGER
		   MAX-ACCESS accessible-for-notify
		   STATUS current
		   DESCRIPTION
              "This variable provides the number of dialogs released in the last minute."
		   ::= { tcapServerAggregateStatistics 4 }					   -- 1.3.6.1.4.1.11150.83.2.4

tcapServerStatLegsReleased			OBJECT-TYPE
		   SYNTAX INTEGER
		   MAX-ACCESS accessible-for-notify
		   STATUS current
		   DESCRIPTION
              "This variable provides the number of legs released in the last minute."
		   ::= { tcapServerAggregateStatistics 5 }					   -- 1.3.6.1.4.1.11150.83.2.5

tcapServerStatDBLookups			OBJECT-TYPE
		   SYNTAX INTEGER
		   MAX-ACCESS accessible-for-notify
		   STATUS current
		   DESCRIPTION
              "This variable provides the number of database lookups attempted in the last minute."
		   ::= { tcapServerAggregateStatistics 6 }					   -- 1.3.6.1.4.1.11150.83.2.6

tcapServerStatDBOpersFailed		OBJECT-TYPE
		   SYNTAX INTEGER
		   MAX-ACCESS accessible-for-notify
		   STATUS current
		   DESCRIPTION
              "This variable provides the number of database operations failed in the last minute."
		   ::= { tcapServerAggregateStatistics 7 }					   -- 1.3.6.1.4.1.11150.83.2.7

tcapServerStatEnDecodeFailed	OBJECT-TYPE
		   SYNTAX INTEGER
		   MAX-ACCESS accessible-for-notify
		   STATUS current
		   DESCRIPTION
              "This variable provides the number of messages failing to encode or decode in the last minute."
		   ::= { tcapServerAggregateStatistics 8 }					   -- 1.3.6.1.4.1.11150.83.2.8

-- Various TCAP Events

tcapServerStatMsgNoDlg			OBJECT-TYPE
		   SYNTAX INTEGER
		   MAX-ACCESS accessible-for-notify
		   STATUS current
		   DESCRIPTION
              "This variable provides the number of times dialog could not be allocated in the last minute."
		   ::= { tcapServerAggregateStatistics 9 }					   -- 1.3.6.1.4.1.11150.83.2.9

tcapServerStatInNwMsg			OBJECT-TYPE
		   SYNTAX INTEGER
		   MAX-ACCESS accessible-for-notify
		   STATUS current
		   DESCRIPTION
              "This variable provides the number of UDT messages received in the last minute."
		   ::= { tcapServerAggregateStatistics 10 }					   -- 1.3.6.1.4.1.11150.83.2.10

tcapServerStatInNwMsgNoService	OBJECT-TYPE
		   SYNTAX INTEGER
		   MAX-ACCESS accessible-for-notify
		   STATUS current
		   DESCRIPTION
              "This variable provides the number of messages received from network matching no service in the last minute."
		   ::= { tcapServerAggregateStatistics 11 }					   -- 1.3.6.1.4.1.11150.83.2.11

tcapServerStatInNwMsgNoInstance	OBJECT-TYPE
		   SYNTAX INTEGER
		   MAX-ACCESS accessible-for-notify
		   STATUS current
		   DESCRIPTION
              "This variable provides the number of times message failed to reach application over spread in the last minute."
		   ::= { tcapServerAggregateStatistics 12 }					   -- 1.3.6.1.4.1.11150.83.2.12

tcapServerStatOutBusMsg			OBJECT-TYPE
		   SYNTAX INTEGER
		   MAX-ACCESS accessible-for-notify
		   STATUS current
		   DESCRIPTION
              "This variable provides the number of messages sent to application in the last minute."
		   ::= { tcapServerAggregateStatistics 13 }					   -- 1.3.6.1.4.1.11150.83.2.13

tcapServerStatOutBusMsgFailed		OBJECT-TYPE
		   SYNTAX INTEGER
		   MAX-ACCESS accessible-for-notify
		   STATUS current
		   DESCRIPTION
              "This variable provides the number of times message processing failed before sending to application in the last minute."
		   ::= { tcapServerAggregateStatistics 14 }					   -- 1.3.6.1.4.1.11150.83.2.14

tcapServerStatInBusMsg		OBJECT-TYPE
		   SYNTAX INTEGER
		   MAX-ACCESS accessible-for-notify
		   STATUS current
		   DESCRIPTION
              "This variable provides the number of messages received from application in the last minute."
		   ::= { tcapServerAggregateStatistics 15 }					   -- 1.3.6.1.4.1.11150.83.2.15

tcapServerStatOutNwMsgSentFailed		OBJECT-TYPE
		   SYNTAX INTEGER
		   MAX-ACCESS accessible-for-notify
		   STATUS current
		   DESCRIPTION
              "This variable provides the number of SCCP messages failed to be sent to network in the last minute."
		   ::= { tcapServerAggregateStatistics 16 }					   -- 1.3.6.1.4.1.11150.83.2.16

tcapServerStatOutNwMsgSent		OBJECT-TYPE
		   SYNTAX INTEGER
		   MAX-ACCESS accessible-for-notify
		   STATUS current
		   DESCRIPTION
              "This variable provides the number of SCCP messages sent to network  in the last minute."
		   ::= { tcapServerAggregateStatistics 17 }					   -- 1.3.6.1.4.1.11150.83.2.17

tcapServerStatOutNwMsgBeginBypassed		OBJECT-TYPE
		   SYNTAX INTEGER
		   MAX-ACCESS accessible-for-notify
		   STATUS current
		   DESCRIPTION
              "This variable provides the number of messages bypassed to SmartSTP in the last minute."
		   ::= { tcapServerAggregateStatistics 18 }					   -- 1.3.6.1.4.1.11150.83.2.18

tcapServerStatOutNwMsgTTbasedRelay		OBJECT-TYPE
		   SYNTAX INTEGER
		   MAX-ACCESS accessible-for-notify
		   STATUS current
		   DESCRIPTION
              "This variable provides the number of messages TT based relayed in the last minute."
		   ::= { tcapServerAggregateStatistics 19 }					   -- 1.3.6.1.4.1.11150.83.2.19

tcapServerStatOutNwMsgBeginInited		OBJECT-TYPE
		   SYNTAX INTEGER
		   MAX-ACCESS accessible-for-notify
		   STATUS current
		   DESCRIPTION
              "This variable provides the number of new legs initiated by application in the last minute."
		   ::= { tcapServerAggregateStatistics 20 }					   -- 1.3.6.1.4.1.11150.83.2.20

tcapServerStatOutNwMsgDefaultAction		OBJECT-TYPE
		   SYNTAX INTEGER
		   MAX-ACCESS accessible-for-notify
		   STATUS current
		   DESCRIPTION
              "This variable provides the number of times default action were taken on the message received from network in the last minute."
		   ::= { tcapServerAggregateStatistics 21 }					   -- 1.3.6.1.4.1.11150.83.2.21

tcapServerStatInNwUDTS		OBJECT-TYPE
		   SYNTAX INTEGER
		   MAX-ACCESS accessible-for-notify
		   STATUS current
		   DESCRIPTION
              "This variable provides the number of UDTS (or xUDTS) message received from network in the last minute."
		   ::= { tcapServerAggregateStatistics 22 }					   -- 1.3.6.1.4.1.11150.83.2.22

tcapServerStatOutNwUDTSSent		OBJECT-TYPE
		   SYNTAX INTEGER
		   MAX-ACCESS accessible-for-notify
		   STATUS current
		   DESCRIPTION
              "This variable provides the number of UDTS (or xUDTS) messages sent to network in the last minute."
		   ::= { tcapServerAggregateStatistics 23 }					   -- 1.3.6.1.4.1.11150.83.2.23

tcapServerCommands OBJECT IDENTIFIER ::= { tcapServer-mob 4 }    -- 1.3.6.1.4.1.11150.83.4

tcapServerRescanOLCData		OBJECT-TYPE
		   SYNTAX INTEGER
		   MAX-ACCESS read-write
		   STATUS current
		   DESCRIPTION
              "This command can be used to rescan overload control data."
		   ::= { tcapServerCommands 1 }					   -- 1.3.6.1.4.1.11150.83.4.1

tcapServerUpdateGTMapping	OBJECT-TYPE
		   SYNTAX INTEGER
		   MAX-ACCESS read-write
		   STATUS current
		   DESCRIPTION
              "This command can be used to add new or update existing GT Mapping."
		   ::= { tcapServerCommands 2 }					   -- 1.3.6.1.4.1.11150.83.4.2

-- Trap variables
tcapServerVariables OBJECT IDENTIFIER ::= { tcapServer-mob 5 }    -- 1.3.6.1.4.1.11150.83.5

tcapServerBusConnId		OBJECT-TYPE
		   SYNTAX OCTET STRING
		   MAX-ACCESS accessible-for-notify
		   STATUS current
		   DESCRIPTION
				"Variable indicating name of the message complex"
		   ::= { tcapServerVariables 1 }					   -- 1.3.6.1.4.1.11150.83.5.1

tcapServerBusConnType	OBJECT-TYPE
		   SYNTAX INTEGER {primary (1), secondary (2)}
		   MAX-ACCESS accessible-for-notify
		   STATUS current
		   DESCRIPTION
				"Indicates primary/secondary connection"
		   ::= { tcapServerVariables 2 }					   -- 1.3.6.1.4.1.11150.83.5.2

--
-- TCAP Server specific traps
--
tcapServerTrapsModule OBJECT IDENTIFIER ::= { tcapServer-mob 3 }	 -- 1.3.6.1.4.1.11150.83.3
tcapServerTrapsGroup OBJECT IDENTIFIER ::= { tcapServerTrapsModule 0 }	   -- 1.3.6.1.4.1.11150.83.3.0

tcapServerSysUp	NOTIFICATION-TYPE
			OBJECTS {   mobGenSequenceNumber, mobGenNotificationId, mobGenSeverity, 
						mobGenDescription, mobGenMachineID, mobGenServiceName, 
						mobGenAlarmTime, mobGenAlarmType, mobGenProbableCause }
			STATUS current
			DESCRIPTION
			"Indicates that the TCAP Server is up and active."
			::= { tcapServerTrapsGroup 1 }

tcapServerSysDown	NOTIFICATION-TYPE
			OBJECTS {   mobGenSequenceNumber, mobGenNotificationId, mobGenSeverity, 
						mobGenDescription, mobGenMachineID, mobGenServiceName, 
						mobGenAlarmTime, mobGenAlarmType, mobGenProbableCause }
			STATUS current
			DESCRIPTION
			"Indicates that the TCAP Server is shutting down."
		::= { tcapServerTrapsGroup 2 }

tcapServerDBConnStatus	NOTIFICATION-TYPE
			OBJECTS {   mobGenSequenceNumber, mobGenNotificationId, mobGenSeverity, 
						mobGenDescription, mobGenMachineID, mobGenServiceName, 
						mobGenAlarmTime, mobGenAlarmType, mobGenProbableCause }
			STATUS current
			DESCRIPTION
			"Indicates the change in connection status of the database server."
			::= { tcapServerTrapsGroup 3 }

tcapServerBusConnStatus	NOTIFICATION-TYPE
			OBJECTS {   mobGenSequenceNumber, mobGenNotificationId, mobGenSeverity, 
						mobGenDescription, mobGenMachineID, mobGenServiceName, 
						mobGenAlarmTime, mobGenAlarmType, mobGenProbableCause,
						tcapServerBusConnId, tcapServerBusConnType }
			STATUS current
			DESCRIPTION
			"Indicates the change in availability status of message complex."
			::= { tcapServerTrapsGroup 4 }

tcapServerDlgThresholdStatus	NOTIFICATION-TYPE
			OBJECTS {   mobGenSequenceNumber, mobGenNotificationId, mobGenSeverity, 
						mobGenDescription, mobGenMachineID, mobGenServiceName, 
						mobGenAlarmTime, mobGenAlarmType, mobGenProbableCause, 
						mobGenThresholdName, mobGenThresholdLWM, mobGenThresholdHWM, 
						mobGenUtilization, mobGenCapacity, mobGenThresholdArmTime }
			STATUS deprecated
			DESCRIPTION
			 "Deprecated - replaced by tcapServerNoDlgThresholdStatus"
			::= { tcapServerTrapsGroup 5 }

tcapServerMsgQThresholdStatus	NOTIFICATION-TYPE
			OBJECTS {   mobGenSequenceNumber, mobGenNotificationId, mobGenSeverity, 
						mobGenDescription, mobGenMachineID, mobGenServiceName, 
						mobGenAlarmTime, mobGenAlarmType, mobGenProbableCause, 
						mobGenThresholdName, mobGenThresholdLWM, mobGenThresholdHWM, 
						mobGenUtilization, mobGenCapacity, mobGenThresholdArmTime }
			STATUS current
			DESCRIPTION
			"Indicates that the number of messages in the message queue has reached the threshold value."
			::= { tcapServerTrapsGroup 6 }

tcapServerSS7ReadNullMsgStatus	NOTIFICATION-TYPE
			OBJECTS {   mobGenSequenceNumber, mobGenNotificationId, mobGenSeverity, 
						mobGenDescription, mobGenMachineID, mobGenServiceName, 
						mobGenAlarmTime, mobGenAlarmType, mobGenProbableCause }
			STATUS current
			DESCRIPTION
			"Indicates whether SS7 card read on the given queue is failing."
			::= { tcapServerTrapsGroup 7 }

tcapServerEnDecodesThresholdStatus	NOTIFICATION-TYPE
			OBJECTS {   mobGenSequenceNumber, mobGenNotificationId, mobGenSeverity, 
						mobGenDescription, mobGenMachineID, mobGenServiceName, 
						mobGenAlarmTime, mobGenAlarmType, mobGenProbableCause, 
						mobGenThresholdName, mobGenThresholdLWM, mobGenThresholdHWM, 
						mobGenUtilization, mobGenCapacity, mobGenThresholdArmTime }
			STATUS current
			DESCRIPTION
			"Indicates the growth of encoding/decoding failures wrt incoming messages."
			::= { tcapServerTrapsGroup 8 }


tcapServerDefaultActsThresholdStatus	NOTIFICATION-TYPE
			OBJECTS {   mobGenSequenceNumber, mobGenNotificationId, mobGenSeverity, 
						mobGenDescription, mobGenMachineID, mobGenServiceName, 
						mobGenAlarmTime, mobGenAlarmType, mobGenProbableCause, 
						mobGenThresholdName, mobGenThresholdLWM, mobGenThresholdHWM, 
						mobGenUtilization, mobGenCapacity, mobGenThresholdArmTime }
			STATUS current
			DESCRIPTION
			"Indicates the growth of default actions taken wrt incoming messages."
			::= { tcapServerTrapsGroup 9 }


tcapServerTrapsResync NOTIFICATION-TYPE
			OBJECTS {   mobGenSequenceNumber, mobGenNotificationId, mobGenSeverity, 
						mobGenDescription, mobGenMachineID, mobGenServiceName, 
						mobGenAlarmTime, mobGenAlarmType, mobGenProbableCause }
			STATUS current
			DESCRIPTION  
			"Indicates the start and end of a trap resync operation."
			::= { tcapServerTrapsGroup 10 }


tcapServerHeartbeat       NOTIFICATION-TYPE
			OBJECTS {   mobGenSequenceNumber, mobGenNotificationId, mobGenSeverity, 
						mobGenDescription, mobGenMachineID, mobGenServiceName, 
						mobGenAlarmTime, mobGenAlarmType, mobGenProbableCause }
			STATUS current
			DESCRIPTION
			"Sent periodically to indicate that Tcap Server is alive"
			::= { tcapServerTrapsGroup 11 }

tcapServerNoDlgThresholdStatus	NOTIFICATION-TYPE
			OBJECTS {   mobGenSequenceNumber, mobGenNotificationId, mobGenSeverity, 
						mobGenDescription, mobGenMachineID, mobGenServiceName, 
						mobGenAlarmTime, mobGenAlarmType, mobGenProbableCause, 
						mobGenThresholdName, mobGenThresholdValue, mobGenUtilization, 
						mobGenCapacity, mobGenThresholdArmTime }
			STATUS current
			DESCRIPTION
			"Indicates that there was no free dialog available for incoming transaction"
			::= { tcapServerTrapsGroup 12 }

END
