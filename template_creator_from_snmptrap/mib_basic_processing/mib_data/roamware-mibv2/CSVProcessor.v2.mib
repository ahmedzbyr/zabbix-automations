--
-- Roamware CSVProcessor MIB definition.
-- Release : 7.0
-- Revision : R100706
-- Revision date : 26-Jul-2010
--
-- This specification is supplied "AS IS," and no warranty,
-- either expressed or implied, as to the use, operation, condition,
-- or performance of the specification, is made by the publisher.
--
-- Publisher: Roamware Inc., USA
-- **************************************************************

Roamware-CSVProcessor-V2-MIB DEFINITIONS ::= BEGIN
IMPORTS
    MODULE-IDENTITY, OBJECT-TYPE, NOTIFICATION-TYPE,
    TimeTicks, Counter32, Integer32
        FROM SNMPv2-SMI
    DisplayString
        FROM SNMPv2-TC
    OBJECT-GROUP
        FROM SNMPv2-CONF
    roamware, mobGenSeverity, mobGenDescription, mobGenPoolName, mobGenMachineID,
    mobGenRemoteHostAddr, mobGenRemotePort, mobGenAlarmTime, mobGenThresholdValue,
    mobGenNotificationId, mobGenServiceName, mobGenAlarmType, mobGenProbableCause,
    mobGenCacheName, mobGenErrorText, mobGenThresholdLWM, mobGenThresholdHWM,
    mobGenThresholdArmTime, mobGenThresholdName, mobGenUtilization, mobGenCapacity,
    mobGenSourcePath, mobGenTargetPath, mobGenSequenceNumber
    FROM Roamware-SDS-V2-MIB;

csvProcessor-mob                MODULE-IDENTITY
                LAST-UPDATED "201007260000Z"
                ORGANIZATION "Roamware Inc."
                CONTACT-INFO "info@roamware.com"
                DESCRIPTION  "This is the top level entry for Roamware CSVProcessor."
                REVISION     "201007260000Z"
                DESCRIPTION  "Initial version."
                ::= { roamware 89 }                                                           -- 1.3.6.1.4.1.11150.89

--
-- CSVProcessor system specific status reports
--
csvProcessorStatus                     OBJECT IDENTIFIER ::= { csvProcessor-mob 1 }           -- 1.3.6.1.4.1.11150.89.1

--
-- CSVProcessor specific traps
--
csvProcessorTrapsModule                OBJECT IDENTIFIER ::= { csvProcessor-mob 2 }           -- 1.3.6.1.4.1.11150.89.2
csvProcessorTrapsGroup                 OBJECT IDENTIFIER ::= { csvProcessorTrapsModule 0 }    -- 1.3.6.1.4.1.11150.89.2.0

csvProcessorSysUp                      NOTIFICATION-TYPE
                OBJECTS { mobGenSequenceNumber, mobGenNotificationId, mobGenSeverity, mobGenDescription, mobGenMachineID,
                          mobGenServiceName, mobGenAlarmTime, mobGenAlarmType, mobGenProbableCause }
                STATUS current
                DESCRIPTION
                "Indicates that the CSVProcessor is up and active."
                ::= { csvProcessorTrapsGroup 1 }

csvProcessorSysDown                    NOTIFICATION-TYPE
                OBJECTS { mobGenSequenceNumber, mobGenNotificationId, mobGenSeverity, mobGenDescription, mobGenMachineID,
                          mobGenServiceName, mobGenAlarmTime, mobGenAlarmType, mobGenProbableCause }
                STATUS current
                DESCRIPTION
                "Indicates that the CSVProcessor is shutting down."
                ::= { csvProcessorTrapsGroup 2 }

csvProcessorDBConnStatus               NOTIFICATION-TYPE
                OBJECTS { mobGenSequenceNumber, mobGenNotificationId, mobGenSeverity, mobGenDescription, mobGenMachineID,
                          mobGenServiceName, mobGenAlarmTime, mobGenAlarmType, mobGenProbableCause }
                STATUS current
                DESCRIPTION
                "Indicates the database connection status."
                ::= { csvProcessorTrapsGroup 3 }

csvProcessorProcessingError            NOTIFICATION-TYPE
                OBJECTS { mobGenSequenceNumber, mobGenNotificationId, mobGenSeverity, mobGenDescription, mobGenMachineID,
                          mobGenServiceName, mobGenAlarmTime, mobGenAlarmType, mobGenProbableCause,
                          mobGenSourcePath }
                STATUS current
                DESCRIPTION
                "Indicates a processing error in CSVProcessor."
                ::= { csvProcessorTrapsGroup 4 }

csvProcessorFileRotateError            NOTIFICATION-TYPE
                OBJECTS   { mobGenSequenceNumber, mobGenNotificationId, mobGenSeverity, mobGenDescription, mobGenMachineID,
			                mobGenServiceName, mobGenAlarmTime, mobGenAlarmType, mobGenProbableCause,
			                mobGenSourcePath, mobGenTargetPath }
                STATUS current
                DESCRIPTION
                "Indicates a problem with file rotation."
                ::= {csvProcessorTrapsGroup 5}

--
-- CSVProcessor system specific statistics
--
csvProcessorStats                      OBJECT IDENTIFIER ::= { csvProcessor-mob 3 }           -- 1.3.6.1.4.1.11150.89.3

csvProcessorRecordsProcessedCount      OBJECT-TYPE
                SYNTAX Integer32
                MAX-ACCESS read-only
                STATUS current
                DESCRIPTION
                "Returns the number of records processed successfully in the last one minute."
                ::= { csvProcessorStats 1 }                                                   -- 1.3.6.1.4.1.11150.89.3.1

csvProcessorRecordsFailedCount         OBJECT-TYPE
                SYNTAX Integer32
                MAX-ACCESS read-only
                STATUS current
                DESCRIPTION
                "Returns the number of records for which processing failed in the last one minute."
                ::= { csvProcessorStats 2 }                                                   -- 1.3.6.1.4.1.11150.89.3.2

csvProcessorMaxRecordProcessTime       OBJECT-TYPE
                SYNTAX Integer32
                MAX-ACCESS read-only
                STATUS current
                DESCRIPTION
                "Returns the maximum processing time in msec of a record in the last one minute."
                ::= { csvProcessorStats 3 }                                                   -- 1.3.6.1.4.1.11150.89.3.3

csvProcessorMinRecordProcessTime       OBJECT-TYPE
                SYNTAX Integer32
                MAX-ACCESS read-only
                STATUS current
                DESCRIPTION
                "Returns the minimum processing time in msec of a record in the last one minute."
                ::= { csvProcessorStats 4 }                                                   -- 1.3.6.1.4.1.11150.89.3.4

csvProcessorMaxFileProcessTime         OBJECT-TYPE
                SYNTAX Integer32
                MAX-ACCESS read-only
                STATUS current
                DESCRIPTION
                "Returns the maximum processing time in msec of a file in the last one minute."
                ::= { csvProcessorStats 5 }                                                   -- 1.3.6.1.4.1.11150.89.3.5

csvProcessorMinFileProcessTime         OBJECT-TYPE
                SYNTAX Integer32
                MAX-ACCESS read-only
                STATUS current
                DESCRIPTION
                "Returns the minimum processing time in msec of a file in the last one minute."
                ::= { csvProcessorStats 6 }                                                   -- 1.3.6.1.4.1.11150.89.3.6

csvProcessorFilesProcessed             OBJECT-TYPE
                SYNTAX Integer32
                MAX-ACCESS read-only
                STATUS current
                DESCRIPTION
                "Returns the number files processed since startup."
                ::= { csvProcessorStats 7 }                                                   -- 1.3.6.1.4.1.11150.89.3.7

END
